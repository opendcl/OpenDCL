;;;
;;; Listenfeld Beispiel
;;;
;;; Dieses Beispiel demonstriert die Anwendung des Listenfelds und seinen Ereignissen.
;;;

;; Hauptprogramm
(defun c:ListBox (/ cmdecho)

	;; Sicherstellen, dass die OpenDCL-Laufzeitumgebung geladen wurde (ohne Meldungen an der Befehlszeile)
	(setq cmdecho (getvar "CMDECHO"))
	(setvar "CMDECHO" 0)
	(command "_OPENDCL")
	(setvar "CMDECHO" cmdecho)

	;; Projekt laden
	(dcl-Project-Load (*ODCL:Samples-FindFile "ListBox.odcl"))

	;; Dialog anzeigen
	(dcl-Form-Show ListBox/Form1)

	;; Dies ist eine modale Dialogbox. Das bedeutet, dass das Programm an dieser
	;; Zeile stehen bleibt und (dcl-Form-Show) solange keinen Wert zurückgibt,
	;; bis der modale Dialog geschlosswen wird.
	;; In der Zwischenzeit übernehmen die Ereignisfunktionen die Dialogsteuerung.

	(princ)
)

;|«OpenDCL Event Handlers»|;

;;----------------------------------------------------
(DEFUN c:ListBox/Form1/SelectFiles#OnClicked (/ bs_filelist fn)
	(SETQ bs_filelist (dcl-multifiledialog "Zeichnungsdateien (*.dwg)|*.dwg||" ; Filter
										   "Dateien auswählen" ; Titel
										   (IF g:lastfolder
											   g:lastfolder
											   (GETVAR "DWGPREFIX")
										   ) ; Default Folder
					  )
	)
	(IF bs_filelist
		(PROGN
			(SETQ g:lastfolder (VL-FILENAME-DIRECTORY (CAR bs_filelist)))
			(FOREACH fn bs_filelist
				(IF (< (dcl-ListBox-FINDSTRINGEXACT ListBox/Form1/ListBox fn) 0)
					(dcl-ListBox-ADDSTRING ListBox/Form1/ListBox fn)
				)
			)
		)
	)
)
;;----------------------------------------------------
(DEFUN c:ListBox/Form1/ClearList#OnClicked (/)
	(dcl-ListBox-CLEAR ListBox/Form1/ListBox)
)
;;----------------------------------------------------
(DEFUN c:ListBox/Form1/Remove#OnClicked (/ rsel item)
	(IF (SETQ rsel (dcl-ListBox-GETSELECTEDNTHS ListBox/Form1/ListBox))
		(PROGN
			(FOREACH item (REVERSE rsel)
				(dcl-ListBox-DELETEITEM ListBox/Form1/ListBox item)
			)
			(SETQ g:bs_filelist '())
			(SETQ item (dcl-ListBox-GETCOUNT ListBox/Form1/ListBox))
			(WHILE (>= (SETQ item (1- item)) 0)
				(SETQ
					g:bs_filelist
					(CONS
						(dcl-ListBox-GETITEMTEXT ListBox/Form1/ListBox item)
						g:bs_filelist
					)
				)
			)
		)
	)
)
;;----------------------------------------------------
(DEFUN c:ListBox/Form1/ExitDialog#OnClicked (/) (dcl-Form-CLOSE ListBox/Form1))

(princ)

;|«OpenDCL Samples Epilog»|;

;;;######################################################################
;;;######################################################################
;;; Der folgende Abschnitt dient dazu, die Beispiel-Dateien zu lokalisieren.
;;; Die Pfadangabe wird um den Abschnitt des Beispielordner, erweitert, der
;;; durch das Installationsprogramm in der Registry eingetragen wurde.
;;; Die globalen Variable *ODCL:Prefix und die Function *ODCL:Samples-FindFile
;;; werden in allen Beispieldateien verwendet.
;;;
(or *ODCL:Samples-FindFile
	(defun *ODCL:Samples-FindFile (file)
		(setq *ODCL:Prefix
			(cond
				(	*ODCL:Prefix
				) ;_ Bereits definiert
				(	(vl-registry-read
						"HKEY_CURRENT_USER\\SOFTWARE\\OpenDCL"
						"SamplesFolder"
					)
				) ;_ 32-bit Variante aktueller Nutzer
				(	(vl-registry-read
						"HKEY_LOCAL_MACHINE\\SOFTWARE\\OpenDCL"
						"SamplesFolder"
					 )
				) ;_ 32-bit Variante alle Nutzer
				(	(vl-registry-read
						"HKEY_LOCAL_MACHINE\\SOFTWARE\\Wow6432Node\\OpenDCL"
						"SamplesFolder"
					)
				) ;_ 64-bit Variante alle Nutzer
			)
		)
		(cond
			((findfile file)) ; überprüfe zunächst den Supportpfad
			(*ODCL:Prefix (findfile (strcat *ODCL:Prefix file)))
			(file)
		)
	)
)

;; Ist der Hauptdialog der OpenDCL-Beispiele aktiv, starte das Beispiel sofort.
;; Andernfalls gib einen Text in der Befehlszeile aus, mit welchem Kommando das Beispiel
;; gestartet werden kann. Auf diesem Wege wird sichergestellt, dass der Name des Beispiels
;; nur an einer Stelle definiert werden muss. Das macht es einfacher, den Code wiederzuverwenden.

(	(lambda (demoname)
		(if *ODCL:AllSamples
			(progn
				(princ (strcat "'" demoname "\n"))
				(apply (read (strcat "C:" demoname)) nil)
			)
			(progn
				(princ (strcat "\n" demoname " OpenDCL-Beispiel ist geladen."))
				(princ (strcat " (Starten Sie das Beispiel mit dem Befehl " (strcase demoname) ")\n"))
			)
		)
	)
	"ListBox"
)
(princ)

;;;######################################################################
;;;######################################################################

;|«Visual LISP© Format Options»
(80 4 50 2 nil "end of " 80 50 0 0 2 nil nil nil T)
;*** DO NOT add text below the comment! ***|;
