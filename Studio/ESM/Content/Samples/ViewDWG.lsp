;;;
;;; Dwg View Sample
;;;
;;; This sample demonstrates the DWG View control.
;;;

;; Main program
(defun c:ViewDwg (/ cmdecho)

	;; Ensure OpenDCL Runtime is (quietly) loaded
	(setq cmdecho (getvar "CMDECHO"))
	(setvar "CMDECHO" 0)
	(command "_OPENDCL")
	(setvar "CMDECHO" cmdecho)

	;; Load the project
	(dcl-Project-Load (*ODCL:Samples-FindFile "ViewDwg.odcl"))

	;; Show the main form
	(dcl-Form-Show ViewDWG/DwgPreview)

	;; This is a modal form, so (dcl-Form-Show) does not return until
	;; the modal form is closed. In the meantime, the event handlers
	;; manage the form.

	(princ)
)

;|*OpenDCL Event Handlers*|;

(defun c:ViewDWG/DwgPreview/Cancel#OnClicked ()
	(dcl-Form-Close ViewDWG/DwgPreview)
)

(defun c:ViewDWG/DwgPreview/Browse#OnClicked ( / )
	(setq sFileName (GetFiled "Select a drawing file" "" "dwg" 8));_ get the path to a dwg file
	(if sFileName
		(progn
			(dcl-DWGPreview-LoadDwg ViewDWG/DwgPreview/ViewDwg sFileName);_ load the DWG Thumbnail preview into the control
			(dcl-BlockView-LoadDwg ViewDWG/DwgPreview/BlockView1 sFileName);_ load the DWG
			(dcl-Control-SetCaption ViewDWG/DwgPreview/Label1 (dcl-DWGPreview-GetDwgName ViewDWG/DwgPreview/ViewDwg));_ show the path of the DWG
			(dcl-Control-SetFocus ViewDWG/DwgPreview/BlockView1)
		)
	)
)

(princ)

;|*OpenDCL Samples Epilog*|;

;;;######################################################################
;;;######################################################################
;;; The following section of code is designed to locate OpenDCL Studio
;;; sample files in the samples folder by prefixing the filename with
;;; the path prefix that was saved in the registry by the installer.
;;; The global *ODCL:Prefix and function *ODCL:Samples-FindFile
;;; are used throughout the samples.
;;;
(or *ODCL:Samples-FindFile
	(defun *ODCL:Samples-FindFile (file)
		(setq *ODCL:Prefix
			(cond
				(	*ODCL:Prefix
				) ;_ already defined
				(	(vl-registry-read
						 "HKEY_CURRENT_USER\\SOFTWARE\\OpenDCL"
						 "SamplesFolder"
					)
				) ;_ 32-bit location
				(	(vl-registry-read
						 "HKEY_LOCAL_MACHINE\\SOFTWARE\\OpenDCL"
						 "SamplesFolder"
					)
				) ;_ 32-bit location
				(	(vl-registry-read
						 "HKEY_LOCAL_MACHINE\\SOFTWARE\\Wow6432Node\\OpenDCL"
						 "SamplesFolder"
					)
				) ;_ 64-bit location
			)
		)
		(cond
			((findfile file)) ; check the support path first
			(*ODCL:Prefix (findfile (strcat *ODCL:Prefix file)))
			(file)
		)
	)
)

;; If AllSamples is active, run the main function immediately; otherwise
;; display a banner. The extra gymnastics allow the sample name to be
;; specified in only one place, thus making it easier to reuse this code.
(	(lambda (demoname)
		(if *ODCL:AllSamples
			(progn
				(princ (strcat "'" demoname "\n"))
				(apply (read (strcat "C:" demoname)) nil)
			)
			(progn
				(princ (strcat "\n" demoname " OpenDCL sample loaded"))
				(princ (strcat " (Enter " (strcase demoname) " command to run)\n"))
			)
		)
	)
	"ViewDwg"
)
(princ)

;;;######################################################################
;;;######################################################################
