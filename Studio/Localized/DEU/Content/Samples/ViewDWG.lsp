;;;
;;; DWG-Vorschau-Beispiel
;;;
;;; Dieses Beispiel demonstriert die Anwendung des DWG-Vorschau-Steuerelements und seinen Ereignissen.
;;;

;; Hauptprogramm
(defun c:ViewDwg (/ cmdecho)

	;; Sicherstellen, dass die OpenDCL-Laufzeitumgebung geladen wurde (ohne Meldungen an der Befehlszeile)
	(setq cmdecho (getvar "CMDECHO"))
	(setvar "CMDECHO" 0)
	(command "_OPENDCL")
	(setvar "CMDECHO" cmdecho)

	;; Projekt laden
	(dcl-Project-Load (*ODCL:Samples-FindFile "ViewDwg.odcl"))

	;; Dialog anzeigen
	(dcl-Form-Show ViewDWG/DwgPreview)

	;; Dies ist eine modale Dialogbox. Das bedeutet, dass das Programm an dieser
	;; Zeile stehen bleibt und (dcl-Form-Show) solange keinen Wert zurückgibt,
	;; bis der modale Dialog geschlosswen wird.
	;; In der Zwischenzeit übernehmen die Ereignisfunktionen die Dialogsteuerung.

	(princ)
)

;|*OpenDCL Event Handlers*|;

(defun c:ViewDWG/DwgPreview/Cancel#OnClicked ()
	(dcl-Form-Close ViewDWG/DwgPreview)
)

(defun c:ViewDWG/DwgPreview/Browse#OnClicked ( / )
	(setq sFileName (GetFiled "Zeichnungsdatei wählen" "" "dwg" 8)); wählt eine Zeichnungsdatei
	(if sFileName
		(progn
			(dcl-DWGPreview-LoadDwg ViewDWG/DwgPreview/ViewDwg sFileName); Lädt das DWG-Vorschaubild in die DWG-Vorschau
			(dcl-BlockView-LoadDwg ViewDWG/DwgPreview/BlockView1 sFileName); Lädt die DWG in die Blockvorschau
			(dcl-Control-SetCaption ViewDWG/DwgPreview/Label1 (dcl-DWGPreview-GetDwgName ViewDWG/DwgPreview/ViewDwg)); Gibt den Pfad der Datei aus
			(dcl-Control-SetFocus ViewDWG/DwgPreview/BlockView1)
		)
	)
)

(princ)

;|*OpenDCL Samples Epilog*|;

;;;######################################################################
;;;######################################################################
;;; Der folgende Abschnitt dient dazu, die Beispiel-Dateien zu lokalisieren.
;;; Die Pfadangabe wird um den Abschnitt des Beispielordner, erweitert, der
;;; durch das Installationsprogramm in der Registry eingetragen wurde.
;;; Die globalen Variable *ODCL:Prefix und die Function *ODCL:Samples-FindFile
;;; werden in allen Beispieldateien verwendet.
;;;
(or *ODCL:Samples-FindFile
	(defun *ODCL:Samples-FindFile (file)
		(setq *ODCL:Prefix
			(cond
				(	*ODCL:Prefix
				) ;_ Bereits definiert
				(	(vl-registry-read
						"HKEY_CURRENT_USER\\SOFTWARE\\OpenDCL"
						"SamplesFolder"
					)
				) ;_ 32-bit Variante aktueller Nutzer
				(	(vl-registry-read
						"HKEY_LOCAL_MACHINE\\SOFTWARE\\OpenDCL"
						"SamplesFolder"
					 )
				) ;_ 32-bit Variante alle Nutzer
				(	(vl-registry-read
						"HKEY_LOCAL_MACHINE\\SOFTWARE\\Wow6432Node\\OpenDCL"
						"SamplesFolder"
					)
				) ;_ 64-bit Variante alle Nutzer
			)
		)
		(cond
			((findfile file)) ; überprüfe zunächst den Supportpfad
			(*ODCL:Prefix (findfile (strcat *ODCL:Prefix file)))
			(file)
		)
	)
)

;; Ist der Hauptdialog der OpenDCL-Beispiele aktiv, starte das Beispiel sofort.
;; Andernfalls gib einen Text in der Befehlszeile aus, mit welchem Kommando das Beispiel
;; gestartet werden kann. Auf diesem Wege wird sichergestellt, dass der Name des Beispiels
;; nur an einer Stelle definiert werden muss. Das macht es einfacher, den Code wiederzuverwenden.

(	(lambda (demoname)
		(if *ODCL:AllSamples
			(progn
				(princ (strcat "'" demoname "\n"))
				(apply (read (strcat "C:" demoname)) nil)
			)
			(progn
				(princ (strcat "\n" demoname " OpenDCL-Beispiel ist geladen."))
				(princ (strcat " (Starten Sie das Beispiel mit dem Befehl " (strcase demoname) ")\n"))
			)
		)
	)
	"ViewDwg"
)
(princ)

;;;######################################################################
;;;######################################################################
